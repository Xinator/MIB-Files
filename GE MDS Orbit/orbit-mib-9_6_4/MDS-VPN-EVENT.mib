MDS-VPN-EVENT DEFINITIONS ::= BEGIN

IMPORTS
    MODULE-IDENTITY,
    OBJECT-TYPE,
    NOTIFICATION-TYPE
        FROM SNMPv2-SMI
    MODULE-COMPLIANCE,
    OBJECT-GROUP,
    NOTIFICATION-GROUP
        FROM SNMPv2-CONF
    mdsEventMIB,
    mdsEventVariablesCeeGroup
        FROM MDS-EVENT-MIB;

mdsVpnEventMIB MODULE-IDENTITY
    LAST-UPDATED "202112060000Z"
    ORGANIZATION
        "GE MDS LLC
        http://www.gemds.com"
    CONTACT-INFO
        "T 1-800-474-0694 (Toll Free in North America)
        T 585-242-9600
        F 585-242-9620

        175 Science Parkway
        Rochester, New York 14620
        USA"
    DESCRIPTION
        "Notifications from authentication"
    REVISION    "202112060000Z"
    DESCRIPTION
        "Initial revision"
    ::= { mdsEventMIB 15 }

mdsVpnEventMIBNotifications OBJECT IDENTIFIER
    ::= { mdsVpnEventMIB 1 }
traps0  OBJECT IDENTIFIER ::= { mdsVpnEventMIBNotifications 1 }
traps   OBJECT IDENTIFIER ::= { traps0 0 }

ipsecVpnConnection NOTIFICATION-TYPE
    STATUS  current
    DESCRIPTION
        "ipsec vpn connection event"
    ::= { traps 1 }

mdsVpnEventMIBConformance  OBJECT IDENTIFIER ::= { mdsVpnEventMIB 3 }
mdsVpnEventMIBCompliances OBJECT IDENTIFIER ::= { mdsVpnEventMIBConformance 1 }
mdsVpnEventMIBGroups      OBJECT IDENTIFIER ::= { mdsVpnEventMIBConformance 2 }

mdsVpnEventMIBCompliance MODULE-COMPLIANCE
    STATUS  current
    DESCRIPTION
        "The compliance statement for SNMP entities that
        implement the MDS-EVENT-MIB."
    MODULE -- this module
        MANDATORY-GROUPS {
            mdsVpnEventNotificationsGroup
        }
        GROUP   mdsEventVariablesCeeGroup
        DESCRIPTION
            "This group is mandatory for SNMP entities that
            support event information encoded in CEE format."
    ::= { mdsVpnEventMIBCompliances 2 }

mdsVpnEventNotificationsGroup  NOTIFICATION-GROUP
    NOTIFICATIONS {
        ipsecVpnConnection
    }
    STATUS  current
    DESCRIPTION
        "The common notifications."
    ::= { mdsVpnEventMIBGroups 1 }

END
