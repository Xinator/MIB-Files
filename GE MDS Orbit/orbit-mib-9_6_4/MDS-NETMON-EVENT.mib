MDS-NETMON-EVENT DEFINITIONS ::= BEGIN

IMPORTS
    MODULE-IDENTITY,
    OBJECT-TYPE,
    NOTIFICATION-TYPE
        FROM SNMPv2-SMI
    MODULE-COMPLIANCE,
    OBJECT-GROUP,
    NOTIFICATION-GROUP
        FROM SNMPv2-CONF
    mdsEventMIB,
    mdsEventVariablesCeeGroup
        FROM MDS-EVENT-MIB;

mdsNetmonEventMIB MODULE-IDENTITY
    LAST-UPDATED "202112060000Z"
    ORGANIZATION
        "GE MDS LLC
        http://www.gemds.com"
    CONTACT-INFO
        "T 1-800-474-0694 (Toll Free in North America)
        T 585-242-9600
        F 585-242-9620

        175 Science Parkway
        Rochester, New York 14620
        USA"
    DESCRIPTION
        "Notifications from authentication"
    REVISION    "202112060000Z"
    DESCRIPTION
        "Initial revision"
    ::= { mdsEventMIB 14 }

mdsNetmonEventMIBNotifications OBJECT IDENTIFIER
    ::= { mdsNetmonEventMIB 1 }
traps0  OBJECT IDENTIFIER ::= { mdsNetmonEventMIBNotifications 1 }
traps   OBJECT IDENTIFIER ::= { traps0 0 }

netmonState NOTIFICATION-TYPE
    STATUS  current
    DESCRIPTION
        "netmon operation state"
    ::= { traps 1 }

mdsNetmonEventMIBConformance  OBJECT IDENTIFIER ::= { mdsNetmonEventMIB 3 }
mdsNetmonEventMIBCompliances OBJECT IDENTIFIER ::= { mdsNetmonEventMIBConformance 1 }
mdsNetmonEventMIBGroups      OBJECT IDENTIFIER ::= { mdsNetmonEventMIBConformance 2 }

mdsNetmonEventMIBCompliance MODULE-COMPLIANCE
    STATUS  current
    DESCRIPTION
        "The compliance statement for SNMP entities that
        implement the MDS-EVENT-MIB."
    MODULE -- this module
        MANDATORY-GROUPS {
            mdsNetmonEventNotificationsGroup
        }
        GROUP   mdsEventVariablesCeeGroup
        DESCRIPTION
            "This group is mandatory for SNMP entities that
            support event information encoded in CEE format."
    ::= { mdsNetmonEventMIBCompliances 2 }

mdsNetmonEventNotificationsGroup  NOTIFICATION-GROUP
    NOTIFICATIONS {
        netmonState
    }
    STATUS  current
    DESCRIPTION
        "The common notifications."
    ::= { mdsNetmonEventMIBGroups 1 }

END
