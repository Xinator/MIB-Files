MDS-MAGNETOMETER-EVENT DEFINITIONS ::= BEGIN

IMPORTS
    MODULE-IDENTITY,
    OBJECT-TYPE,
    NOTIFICATION-TYPE
        FROM SNMPv2-SMI
    MODULE-COMPLIANCE,
    OBJECT-GROUP,
    NOTIFICATION-GROUP
        FROM SNMPv2-CONF
    mdsEventMIB,
    mdsEventVariablesCeeGroup
        FROM MDS-EVENT-MIB;

mdsMagnetometerEventMIB MODULE-IDENTITY
    LAST-UPDATED "202112060000Z"
    ORGANIZATION
        "GE MDS LLC
        http://www.gemds.com"
    CONTACT-INFO
        "T 1-800-474-0694 (Toll Free in North America)
        T 585-242-9600
        F 585-242-9620

        175 Science Parkway
        Rochester, New York 14620
        USA"
    DESCRIPTION
        "Notifications from the cellular interface"
    REVISION    "202112060000Z"
    DESCRIPTION
        "Initial revision"
    ::= { mdsEventMIB 10 }

mdsMagnetometerEventMIBNotifications OBJECT IDENTIFIER
    ::= { mdsMagnetometerEventMIB 1 }
traps0  OBJECT IDENTIFIER ::= { mdsMagnetometerEventMIBNotifications 1 }
traps   OBJECT IDENTIFIER ::= { traps0 0 }

tamperDetected NOTIFICATION-TYPE
    STATUS  current
    DESCRIPTION
        "tamperDetected"
    ::= { traps 1 }

mdsMagnetometerEventMIBConformance  OBJECT IDENTIFIER ::= { mdsMagnetometerEventMIB 3 }
mdsMagnetometerEventMIBCompliances OBJECT IDENTIFIER ::= { mdsMagnetometerEventMIBConformance 1 }
mdsMagnetometerEventMIBGroups      OBJECT IDENTIFIER ::= { mdsMagnetometerEventMIBConformance 2 }

mdsMagnetometerEventMIBCompliance MODULE-COMPLIANCE
    STATUS  current
    DESCRIPTION
        "The compliance statement for SNMP entities that
        implement the MDS-EVENT-MIB."
    MODULE -- this module
        MANDATORY-GROUPS {
            mdsMagnetometerEventNotificationsGroup
        }
        GROUP   mdsEventVariablesCeeGroup
        DESCRIPTION
            "This group is mandatory for SNMP entities that
            support event information encoded in CEE format."
    ::= { mdsMagnetometerEventMIBCompliances 2 }

mdsMagnetometerEventNotificationsGroup  NOTIFICATION-GROUP
    NOTIFICATIONS {
        tamperDetected
    }
    STATUS  current
    DESCRIPTION
        "The common notifications."
    ::= { mdsMagnetometerEventMIBGroups 1 }

END
