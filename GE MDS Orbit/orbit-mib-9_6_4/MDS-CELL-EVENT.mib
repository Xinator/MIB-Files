MDS-CELL-EVENT DEFINITIONS ::= BEGIN

IMPORTS
    MODULE-IDENTITY,
    OBJECT-TYPE,
    NOTIFICATION-TYPE
        FROM SNMPv2-SMI
    MODULE-COMPLIANCE,
    OBJECT-GROUP,
    NOTIFICATION-GROUP
        FROM SNMPv2-CONF
    mdsEventMIB,
    mdsEventVariablesCeeGroup
        FROM MDS-EVENT-MIB;

mdsCellEventMIB MODULE-IDENTITY
    LAST-UPDATED "202112060000Z"
    ORGANIZATION
        "GE MDS LLC
        http://www.gemds.com"
    CONTACT-INFO
        "T 1-800-474-0694 (Toll Free in North America)
        T 585-242-9600
        F 585-242-9620

        175 Science Parkway
        Rochester, New York 14620
        USA"
    DESCRIPTION
        "Notifications from the cellular interface"
    REVISION    "202112060000Z"
    DESCRIPTION
        "Initial revision"
    ::= { mdsEventMIB 5 }

mdsCellEventMIBNotifications OBJECT IDENTIFIER
    ::= { mdsCellEventMIB 1 }
traps0  OBJECT IDENTIFIER ::= { mdsCellEventMIBNotifications 1 }
traps   OBJECT IDENTIFIER ::= { traps0 0 }

cellConnected NOTIFICATION-TYPE
    STATUS  current
    DESCRIPTION
        "cell connection established"
    ::= { traps 1 }

cellDisconnected NOTIFICATION-TYPE
    STATUS  current
    DESCRIPTION
        "cell connection disconnected"
    ::= { traps 2 }

cellRecovery NOTIFICATION-TYPE
    STATUS  current
    DESCRIPTION
        "cell recovery initiated"
    ::= { traps 3 }

cellServiceChange NOTIFICATION-TYPE
    STATUS  current
    DESCRIPTION
        "cell service state changed"
    ::= { traps 4 }

cellRoamingChange NOTIFICATION-TYPE
    STATUS  current
    DESCRIPTION
        "cell roaming state changed"
    ::= { traps 5 }

cellSimChange NOTIFICATION-TYPE
    STATUS  current
    DESCRIPTION
        "cell sim state changed"
    ::= { traps 6 }

mdsCellEventMIBConformance  OBJECT IDENTIFIER ::= { mdsCellEventMIB 3 }
mdsCellEventMIBCompliances OBJECT IDENTIFIER ::= { mdsCellEventMIBConformance 1 }
mdsCellEventMIBGroups      OBJECT IDENTIFIER ::= { mdsCellEventMIBConformance 2 }

mdsCellEventMIBCompliance MODULE-COMPLIANCE
    STATUS  current
    DESCRIPTION
        "The compliance statement for SNMP entities that
        implement the MDS-EVENT-MIB."
    MODULE -- this module
        MANDATORY-GROUPS {
            mdsCellEventNotificationsGroup
        }
        GROUP   mdsEventVariablesCeeGroup
        DESCRIPTION
            "This group is mandatory for SNMP entities that
            support event information encoded in CEE format."
    ::= { mdsCellEventMIBCompliances 2 }

mdsCellEventNotificationsGroup  NOTIFICATION-GROUP
    NOTIFICATIONS {
        cellConnected,
        cellDisconnected,
        cellRecovery,
        cellServiceChange,
        cellRoamingChange,
        cellSimChange
    }
    STATUS  current
    DESCRIPTION
        "The common notifications."
    ::= { mdsCellEventMIBGroups 1 }

END
