MDS-WIFI-EVENT DEFINITIONS ::= BEGIN

IMPORTS
    MODULE-IDENTITY,
    OBJECT-TYPE,
    NOTIFICATION-TYPE
        FROM SNMPv2-SMI
    MODULE-COMPLIANCE,
    OBJECT-GROUP,
    NOTIFICATION-GROUP
        FROM SNMPv2-CONF
    mdsEventMIB,
    mdsEventVariablesCeeGroup
        FROM MDS-EVENT-MIB;

mdsWifiEventMIB MODULE-IDENTITY
    LAST-UPDATED "202112060000Z"
    ORGANIZATION
        "GE MDS LLC
        http://www.gemds.com"
    CONTACT-INFO
        "T 1-800-474-0694 (Toll Free in North America)
        T 585-242-9600
        F 585-242-9620

        175 Science Parkway
        Rochester, New York 14620
        USA"
    DESCRIPTION
        "Notifications from the WiFi interface"
    REVISION    "202112060000Z"
    DESCRIPTION
        "Initial revision"
    ::= { mdsEventMIB 6 }

mdsWifiEventMIBNotifications OBJECT IDENTIFIER
    ::= { mdsWifiEventMIB 1 }
traps0  OBJECT IDENTIFIER ::= { mdsWifiEventMIBNotifications 1 }
traps   OBJECT IDENTIFIER ::= { traps0 0 }

wifiStationConnect NOTIFICATION-TYPE
    STATUS  current
    DESCRIPTION
        "station connected to access point"
    ::= { traps 1 }

wifiStationDisconnect NOTIFICATION-TYPE
    STATUS  current
    DESCRIPTION
        "station disconnected from access point"
    ::= { traps 2 }

mdsWifiEventMIBConformance  OBJECT IDENTIFIER ::= { mdsWifiEventMIB 3 }
mdsWifiEventMIBCompliances OBJECT IDENTIFIER ::= { mdsWifiEventMIBConformance 1 }
mdsWifiEventMIBGroups      OBJECT IDENTIFIER ::= { mdsWifiEventMIBConformance 2 }

mdsWifiEventMIBCompliance MODULE-COMPLIANCE
    STATUS  current
    DESCRIPTION
        "The compliance statement for SNMP entities that
        implement the MDS-EVENT-MIB."
    MODULE -- this module
        MANDATORY-GROUPS {
            mdsWifiEventNotificationsGroup
        }
        GROUP   mdsEventVariablesCeeGroup
        DESCRIPTION
            "This group is mandatory for SNMP entities that
            support event information encoded in CEE format."
    ::= { mdsWifiEventMIBCompliances 2 }

mdsWifiEventNotificationsGroup  NOTIFICATION-GROUP
    NOTIFICATIONS {
        wifiStationConnect,
        wifiStationDisconnect
    }
    STATUS  current
    DESCRIPTION
        "The common notifications."
    ::= { mdsWifiEventMIBGroups 1 }

END
