MDS-DEFAULT-EVENT DEFINITIONS ::= BEGIN

IMPORTS
    MODULE-IDENTITY,
    OBJECT-TYPE,
    NOTIFICATION-TYPE
        FROM SNMPv2-SMI
    MODULE-COMPLIANCE,
    OBJECT-GROUP,
    NOTIFICATION-GROUP
        FROM SNMPv2-CONF
    mdsEventMIB,
    mdsEventVariablesCeeGroup
        FROM MDS-EVENT-MIB;

mdsDefaultEventMIB MODULE-IDENTITY
    LAST-UPDATED "202112060000Z"
    ORGANIZATION
        "GE MDS LLC
        http://www.gemds.com"
    CONTACT-INFO
        "T 1-800-474-0694 (Toll Free in North America)
        T 585-242-9600
        F 585-242-9620

        175 Science Parkway
        Rochester, New York 14620
        USA"
    DESCRIPTION
        "Notifications from Orbit"
    REVISION    "202112060000Z"
    DESCRIPTION
        "Initial revision"
    ::= { mdsEventMIB 3 }

mdsDefaultEventMIBNotifications OBJECT IDENTIFIER
    ::= { mdsDefaultEventMIB 1 }
traps0  OBJECT IDENTIFIER ::= { mdsDefaultEventMIBNotifications 1 }
traps   OBJECT IDENTIFIER ::= { traps0 0 }

internalSoftwareError NOTIFICATION-TYPE
    STATUS  current
    DESCRIPTION
        "Internal software error"
    ::= { traps 1 }

internalSoftwareWarning NOTIFICATION-TYPE
    STATUS  current
    DESCRIPTION
        "Internal software warning"
    ::= { traps 2 }

slabMemoryWarning NOTIFICATION-TYPE
    STATUS  current
    DESCRIPTION
        "Slab Memory Warning"
    ::= { traps 3 }

info NOTIFICATION-TYPE
    STATUS  current
    DESCRIPTION
        "Internal information events"
    ::= { traps 4 }

debug NOTIFICATION-TYPE
    STATUS  current
    DESCRIPTION
        "Internal debugging events"
    ::= { traps 5 }

consoleLogin NOTIFICATION-TYPE
    STATUS  current
    DESCRIPTION
        "consoleLogin"
    ::= { traps 6 }

consoleLogout NOTIFICATION-TYPE
    STATUS  current
    DESCRIPTION
        "consoleLogout"
    ::= { traps 7 }

sshLogin NOTIFICATION-TYPE
    STATUS  current
    DESCRIPTION
        "sshLogin"
    ::= { traps 8 }

sshLogout NOTIFICATION-TYPE
    STATUS  current
    DESCRIPTION
        "sshLogout"
    ::= { traps 9 }

webLogin NOTIFICATION-TYPE
    STATUS  current
    DESCRIPTION
        "webLogin"
    ::= { traps 10 }

webLogout NOTIFICATION-TYPE
    STATUS  current
    DESCRIPTION
        "webLogout"
    ::= { traps 11 }

netconfLogin NOTIFICATION-TYPE
    STATUS  current
    DESCRIPTION
        "netconfLogin"
    ::= { traps 12 }

netconfLogout NOTIFICATION-TYPE
    STATUS  current
    DESCRIPTION
        "netconfLogout"
    ::= { traps 13 }

terminalServerConnect NOTIFICATION-TYPE
    STATUS  current
    DESCRIPTION
        "terminalServerConnect"
    ::= { traps 14 }

hardwareError NOTIFICATION-TYPE
    STATUS  current
    DESCRIPTION
        "hardwareError"
    ::= { traps 15 }

systemBoot NOTIFICATION-TYPE
    STATUS  current
    DESCRIPTION
        "systemBoot"
    ::= { traps 16 }

settingsChange NOTIFICATION-TYPE
    STATUS  current
    DESCRIPTION
        "System configuration has changed"
    ::= { traps 17 }

systemBootError NOTIFICATION-TYPE
    STATUS  current
    DESCRIPTION
        "Boot Error"
    ::= { traps 18 }

netconfConfirmedCommit NOTIFICATION-TYPE
    STATUS  current
    DESCRIPTION
        "A NETCONF confirmed commit event"
    ::= { traps 19 }

eventLogCleared NOTIFICATION-TYPE
    STATUS  current
    DESCRIPTION
        "The event log was cleared by a user"
    ::= { traps 20 }

eventlogHighWater NOTIFICATION-TYPE
    STATUS  current
    DESCRIPTION
        "System eventlog has reached the high-water mark"
    ::= { traps 21 }

eventlogFull NOTIFICATION-TYPE
    STATUS  current
    DESCRIPTION
        "System eventlog is full"
    ::= { traps 22 }

onetimepassword NOTIFICATION-TYPE
    STATUS  current
    DESCRIPTION
        "One-Time-Password activity"
    ::= { traps 23 }

onetimepasswordUnset NOTIFICATION-TYPE
    STATUS  current
    DESCRIPTION
        "One-Time-Password Unset"
    ::= { traps 24 }

ddnsUpdate NOTIFICATION-TYPE
    STATUS  current
    DESCRIPTION
        "DDNS update"
    ::= { traps 25 }

invalidConfiguration NOTIFICATION-TYPE
    STATUS  current
    DESCRIPTION
        "Invalid configuraion"
    ::= { traps 26 }

fips NOTIFICATION-TYPE
    STATUS  current
    DESCRIPTION
        "FIPS 140-2 Operational Compliance"
    ::= { traps 27 }

ztpRegistration NOTIFICATION-TYPE
    STATUS  current
    DESCRIPTION
        "ZTP registration"
    ::= { traps 28 }

testAlarm NOTIFICATION-TYPE
    STATUS  current
    DESCRIPTION
        "Test Alarm"
    ::= { traps 29 }

mdsDefaultEventMIBConformance  OBJECT IDENTIFIER ::= { mdsDefaultEventMIB 3 }
mdsDefaultEventMIBCompliances OBJECT IDENTIFIER ::= { mdsDefaultEventMIBConformance 1 }
mdsDefaultEventMIBGroups      OBJECT IDENTIFIER ::= { mdsDefaultEventMIBConformance 2 }

mdsDefaultEventMIBCompliance MODULE-COMPLIANCE
    STATUS  current
    DESCRIPTION
        "The compliance statement for SNMP entities that
        implement the MDS-EVENT-MIB."
    MODULE -- this module
        MANDATORY-GROUPS {
            mdsDefaultEventNotificationsGroup
        }
        GROUP   mdsEventVariablesCeeGroup
        DESCRIPTION
            "This group is mandatory for SNMP entities that
            support event information encoded in CEE format."
    ::= { mdsDefaultEventMIBCompliances 2 }

mdsDefaultEventNotificationsGroup  NOTIFICATION-GROUP
    NOTIFICATIONS {
        internalSoftwareError,
        internalSoftwareWarning,
        slabMemoryWarning,
        info,
        debug,
        consoleLogin,
        consoleLogout,
        sshLogin,
        sshLogout,
        webLogin,
        webLogout,
        netconfLogin,
        netconfLogout,
        terminalServerConnect,
        hardwareError,
        systemBoot,
        settingsChange,
        systemBootError,
        netconfConfirmedCommit,
        eventLogCleared,
        eventlogHighWater,
        eventlogFull,
        onetimepassword,
        onetimepasswordUnset,
        ddnsUpdate,
        invalidConfiguration,
        fips,
        ztpRegistration,
        testAlarm
    }
    STATUS  current
    DESCRIPTION
        "The common notifications."
    ::= { mdsDefaultEventMIBGroups 1 }

END
